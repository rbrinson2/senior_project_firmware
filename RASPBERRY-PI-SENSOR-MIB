RASPBERRY-PI-SENSOR-MIB DEFINITIONS ::= BEGIN

IMPORTS
    MODULE-IDENTITY, OBJECT-TYPE, OBJECT-IDENTITY,
    enterprises, Integer32, Counter32, Gauge32
        FROM SNMPv2-SMI
    MODULE-COMPLIANCE, OBJECT-GROUP
        FROM SNMPv2-CONF
    DisplayString
        FROM SNMPv2-TC;

raspberryPiSensorMIB MODULE-IDENTITY
    LAST-UPDATED "202508310000Z"
    ORGANIZATION "Home Lab"
    CONTACT-INFO
        "Contact: admin@example.com
         Description: Custom MIB for Raspberry Pi sensor monitoring"
    DESCRIPTION
        "This MIB module defines objects for monitoring custom sensors
         connected to a Raspberry Pi device."
    REVISION "202508310000Z"
    DESCRIPTION
        "Initial version of the Raspberry Pi Sensor MIB."
    ::= { enterprises 75}

-- Main MIB structure
raspberryPiSensors OBJECT-IDENTITY
    STATUS current
    DESCRIPTION
        "Root object for Raspberry Pi sensor monitoring"
    ::= { raspberryPiSensorMIB 1 }

-- Sensor data group
sensorData OBJECT-IDENTITY
    STATUS current
    DESCRIPTION
        "Group containing sensor measurement data"
    ::= { raspberryPiSensors 1 }

-- Sensor status group
sensorStatus OBJECT-IDENTITY
    STATUS current
    DESCRIPTION
        "Group containing sensor status information"
    ::= { raspberryPiSensors 2 }

-- Current Reading
sensorCurrent OBJECT-TYPE
    SYNTAX Integer32 (-15000..15000)
    UNITS "miliAmps"
    MAX-ACCESS read-only
    STATUS current
    DESCRIPTION
        "Reading of the current value from -15A to 15A at 1.25mA intervals. Passes these values as integer with 3 decimal places of precision"
    ::= { sensorData 1 }

-- Voltage Reading
sensorVoltage OBJECT-TYPE
    SYNTAX Integer32 (0..40960)
    UNITS "miliVolts"
    MAX-ACCESS read-only
    STATUS current
    DESCRIPTION
        "Reading of the voltage value from 0V to 40.96V in 1.25mV increments. Passes values as integer with 3 decimal places of precision."
    ::= { sensorData 2 }

-- Power Reading
sensorPower OBJECT-TYPE
    SYNTAX Integer32 (0..41943)
    UNITS "miliWatts"
    MAX-ACCESS read-only
    STATUS current
    DESCRIPTION
        "Reading of the power from 0W to 419.430W in 10mW increments. Does not provide negative power reading and provides 2 decimal places of precision"
    ::= { sensorData 3 }

-- Sensor name/description
sensorDescription OBJECT-TYPE
    SYNTAX DisplayString (SIZE (0..255))
    MAX-ACCESS read-only
    STATUS current
    DESCRIPTION
        "Ina260"
    ::= { sensorData 4 }

-- Sensory Address
sensorAddress OBJECT-TYPE
    SYNTAX DisplayString (SIZE (0..255))
    MAX-ACCESS read-only
    STATUS current
    DESCRIPTION
        "I2C address of Ina260 sensor"
    ::= { sensorData 5 }

-- Last update timestamp
sensorLastUpdate OBJECT-TYPE
    SYNTAX Integer32
    UNITS "seconds"
    MAX-ACCESS read-only
    STATUS current
    DESCRIPTION
        "Unix timestamp of the last sensor reading update"
    ::= { sensorData 6 }

-- Sensor status
sensorOperationalStatus OBJECT-TYPE
    SYNTAX INTEGER {
        unknown(1),
        operational(2),
        warning(3),
        critical(4),
        offline(5)
    }
    MAX-ACCESS read-only
    STATUS current
    DESCRIPTION
        "Current operational status of the sensor"
    ::= { sensorStatus 1 }

-- Error count
sensorErrorCount OBJECT-TYPE
    SYNTAX Counter32
    MAX-ACCESS read-only
    STATUS current
    DESCRIPTION
        "Total number of sensor read errors since last reset"
    ::= { sensorStatus 2 }

-- Sensor uptime
sensorUptime OBJECT-TYPE
    SYNTAX Integer32
    UNITS "seconds"
    MAX-ACCESS read-only
    STATUS current
    DESCRIPTION
        "Time in seconds since the sensor was last initialized"
    ::= { sensorStatus 3 }

-- GPU data group
gpuData OBJECT-IDENTITY
    STATUS current
    DESCRIPTION
        "Group containing GPU data"
    ::= { raspberryPiSensors 3 }

gpuPowerLimit OBJECT-TYPE
    SYNTAX UInteger32 (0..500)
    UNITS "Watts"
    MAX-ACCESS read-write
    STATUS current
    DESCRIPTION
        "The current power limit of the GPU"
    ::= { gpuData 1 }



-- Conformance information
raspberryPiSensorConformance OBJECT-IDENTITY
    STATUS current
    DESCRIPTION
        "Conformance information for the Raspberry Pi Sensor MIB"
    ::= { raspberryPiSensorMIB 2 }

raspberryPiSensorCompliances OBJECT-IDENTITY
    STATUS current
    DESCRIPTION
        "Compliance statements"
    ::= { raspberryPiSensorConformance 1 }

raspberryPiSensorGroups OBJECT-IDENTITY
    STATUS current
    DESCRIPTION
        "MIB groups"
    ::= { raspberryPiSensorConformance 2 }

-- Compliance statement
raspberryPiSensorCompliance MODULE-COMPLIANCE
    STATUS current
    DESCRIPTION
        "The compliance statement for entities implementing the
         Raspberry Pi Sensor MIB"
    MODULE
        MANDATORY-GROUPS {
            raspberryPiSensorDataGroup,
            raspberryPiSensorStatusGroup,
            raspberryPiGPUControlGroup
        }
    ::= { raspberryPiSensorCompliances 1 }

-- Object groups
raspberryPiSensorDataGroup OBJECT-GROUP
    OBJECTS {
        sensorCurrent,
        sensorVoltage,
        sensorPower,
        sensorDescription,
        sensorAddress,
        sensorLastUpdate
    }
    STATUS current
    DESCRIPTION
        "A collection of objects providing sensor data information"
    ::= { raspberryPiSensorGroups 1 }

raspberryPiSensorStatusGroup OBJECT-GROUP
    OBJECTS {
        sensorOperationalStatus,
        sensorErrorCount,
        sensorUptime
    }
    STATUS current
    DESCRIPTION
        "A collection of objects providing sensor status information"
    ::= { raspberryPiSensorGroups 2 }

raspberryPiGPUControlGroup OBJECT-GROUP
    OBJECTS {
        gpuPowerLimit
    }
    STATUS current
    DESCRIPTION
        "A collection of GPU monitoring commands"
    ::= { raspberryPiSensorGroups 3}
END
